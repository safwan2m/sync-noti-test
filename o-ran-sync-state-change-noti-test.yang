module o-ran-sync-state-change-noti-test {
  yang-version 1.1;
  namespace "urn:o-ran:sync-noti-test:1.0";
  prefix "o-ran-sync-state-change-noti-test";

  description
    "This module is a test module to test the sync-state change notificatioin";

  revision "2025-05-15" {
    description
      "version 1.0.0

      1) This YANG is only for testing the sync state notification and does not depend on any other YANGs.";
    reference "v1.0.0";
  }

  typedef sync-state-type {
    type enumeration {
      enum LOCKED {
        description "Equipment is in the locked mode, as defined in ITU-T G.810.";
      }
      enum HOLDOVER {
        description "Equipment clock is in holdover mode.";
      }
      enum FREERUN {
        description "Equipment clock isn't locked to an input reference, and is not in the holdover mode.";
      }
    }
    description "Enumeration of synchronization states.";
  }

  grouping sync-group {
    description "This group represents the state and status of timing and synchronization of the O-RU.";
    container sync-status {
      config false;
      description
        "Object of this class provides synchronization state of the module.";

      leaf sync-state {
        type sync-state-type;
        mandatory true;
        description "State of DU synchronization.";
      }
    }
  }

  container sync-noti-test {
    description "Main container for synchronization-related parameters.";
    uses sync-group;
  }

  notification synchronization-state-change {
    description
      "Notification used to inform about synchronization state change.";

    leaf sync-state {
      type sync-state-type;
      description
        "State of equipment synchronization is notified at state change.";
    }
  }
}
